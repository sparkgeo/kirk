FME workspace APP_KIRK__FGDB.fmw
Startup Python:
      import fme
      import DataBCFMWTemplate
      start = DataBCFMWTemplate.Start(fme)
      start.startup()
Shutdown Python:
      import fme
      import DataBCFMWTemplate
      shutIt = DataBCFMWTemplate.Shutdown(fme)
      shutIt.shutdown()

Parameters:
- TEXT = 370   # KIRK_JOBID The APP_KIRK Job id
- FILE_CHANGE_DETECTION = TRUE   # Set to TRUE to enable (else disable) change detection
- TEXT =   # KIRK_JOBLABEL descriptive label that is used to help understand what the job is
- KIRK_DEST_DB_KEY_OVERRIDE =   # Override Destination Database Environment Key
- SRC_FEATURE_1:   # Python Script
      import KIRKParams
      import fme
      params = KIRKParams.KIRKParams(fme.macroValues)
      return params.getSourceFeatureClass()
- SRC_DATASET_FGDB_1:   # Python Script
      import fme
      import KIRKParams
      params = KIRKParams.KIRKParams(fme.macroValues)
      return params.getSourceFilePath()
- LOGFILE:   # Python Script
      import DataBCFMWTemplate
      params = DataBCFMWTemplate.CalcParams(FME_MacroValues)
      logfilepath = params.getFMWLogFileRelativePath()
      print 'logfilepath', logfilepath
      return logfilepath
- DEST_SDE_CONNFILE:   # Python Script
      import DataBCFMWTemplate
      params = DataBCFMWTemplate.CalcParams(FME_MacroValues)
      return params.getDestDatabaseConnectionFilePath()
- KIRK_FLDMAPCSVPATH:   # Python Script
      import fme
      import KIRKParams
      params = KIRKParams.KIRKParams(fme.macroValues)
      csvFile = params.getFieldMapAsCSV()
      print 'csvFile', csvFile
      return csvFile
- KIRK_COUNTERCNT:   # Python Script
      import fme
      import KIRKParams
      params = KIRKParams.KIRKParams(fme.macroValues)
      cnt = params.getCounterTransformersCount()
      print 'counter trans cnt', cnt
      return cnt
- KIRK_COUNTERSTART:   # Python Script
      import fme
      import KIRKParams
      params = KIRKParams.KIRKParams(fme.macroValues)
      counterStart = params.getCounterTransformerParameters('counterStartNumber')
      print 'counterStart', counterStart
      return counterStart
- KIRK_COUNTERSCOPE:   # Python Script
      import fme
      import KIRKParams
      params = KIRKParams.KIRKParams(fme.macroValues)
      return params.getCounterTransformerParameters('counterScope')
- KIRK_COUNTERNAME:   # Python Script
      import fme
      import KIRKParams
      params = KIRKParams.KIRKParams(fme.macroValues)
      counterName = params.getCounterTransformerParameters('counterName')
      print 'counterName', counterName
      return counterName
- SRC_PROJECTION:   # Python Script
      import fme
      import KIRKParams
      params = KIRKParams.KIRKParams(fme.macroValues)
      return params.getSourceProjection()

Readers:
- GEODATABASE_FILE_1: GEODATABASE_FILE from $(SRC_DATASET_FGDB_1) in $(SRC_PROJECTION)
- CSV2_1: CSV2 from $(KIRK_FLDMAPCSVPATH)
- GEODATABASE_SDE_1: GEODATABASE_SDE

Writers:
- GEODATABASE_SDE_2: GEODATABASE_SDE in BCALB-83

County (reader GEODATABASE_FILE_1)
    attributes: OBJECTID integer, LGL_ADMIN_AREA_ID integer, UPDATE_TYPE char(20), IS_PUBLIC char(1), ADMIN_AREA_NAME char(200), ADMIN_AREA_BOUNDARY_TYPE char(20), ADMIN_AREA_ABBREVIATION char(40), CHANGE_REQUESTED_ORG char(30), ADMIN_AREA_TYPE_DESC char(50), UPDATE_DATE date, UPDATE_USERID char(10), ADMIN_AREA_PARENT_NAME char(200), OIC_NUMBER char(7), OIC_YEAR char(4), AFFECTED_ADMIN_AREA_ABRVN char(120), SHAPE_Length double, SHAPE_Area double
    -> File_Change_Detector_v2 [FILE_SOURCE]
Note: Jobs to test with: / 101 - no trans, yes fieldmaps / 20 - no trans, no fildmaps / 21 - no trans, yes fieldmaps, BIGGER DATA 400,000 / 26 - yes trans, no fldmap / 4 - no trans, yes fldmap / 12 - yes, yes / 42
Note: TODO: / - tester for fieldmaps, different path for no fieldmaps - DONE / - Add counter transformer forks - DONE / - Add failed features functionality / - Add Projections to source / dest - DONE
File_Change_Detector_v2: File Change Detector v2
    CHANGES -> ParameterFetcher
ParameterFetcher
    ATTR_LIST = _DEST_FEATURE_1 $(DEST_FEATURE_1)
    -> HasCounter_Tester
HasCounter_Tester: Tester
    TEST_CLAUSE = TEST $(KIRK_COUNTERCNT) > 0
    TEST_MODE = Automatic
    BOOL_OP = OR
    TEST_DESCRIPTION = ""
    PASSED -> Counter
    FAILED -> ArcStroker
Counter
    START = $(KIRK_COUNTERSTART)
    DOMAIN = $(KIRK_COUNTERNAME)
    CNT_ATTR = KIRK_TMP_COUNTER_ATTRIBUTE
    SCOPE = $(KIRK_COUNTERSCOPE)
    -> ArcStroker
ArcStroker
    STROKE_CHOICE = Maximum Deviation
    TOLERANCE_VAL = 0.1
    MAKE_POLY = No
    STROKED -> KirkSchemaMapper
KirkSchemaMapper: PythonCaller
    PYTHONSYMBOL = FeatureProcessor
    PYTHONSOURCE:
      import fme
      import fmeobjects

      import pyKirkFieldMapper
      print 'imports worked'
      class FeatureProcessor(pyKirkFieldMapper.FeatureProcessor):

          def __init__(self):
              print 'init called'
              pyKirkFieldMapper.FeatureProcessor.__init__(self, fme)
              print 'init completed'
    -> FeatureClass1 (writer GEODATABASE_SDE_2)
FeatureClass1 (writer GEODATABASE_SDE_2)
